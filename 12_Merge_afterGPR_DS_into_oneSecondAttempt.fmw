FME workspace 12_Merge_afterGPR_DS_into_oneSecondAttempt.fmw

Parameters:
- DestDataset_CSV2 = $(FME_MF_DIR)csv_afterGPR2   # Destination CSV (Comma Separated Value) Folder
- SourceDataset_CSV2 = ""$(FME_MF_DIR)csv_afterGPR\**\*.csv" "$(FME_MF_DIR)csv_afterGPR\*.gz" "$(FME_MF_DIR)csv_afterGPR\*.txt""   # Source CSV (Comma Separated Value) File(s)
- no =

Readers:
- CSV2_1: CSV2 from $(SourceDataset_CSV2)

Writers:
- CSV2_2: CSV2 to $(DestDataset_CSV2)

CSV (reader CSV2_1)
    attributes: IDSession string, DistanceStamp string, Scan string, Lat(°) string, Long(°) string, Layer 1 2-Way Time string, Layer 1 Layer Diel. string, Layer 1 Depth(in) string, Layer 2 2-Way Time string, Layer 2 Layer Diel. string, Layer 2 Depth(in) string, Layer 3 2-Way Time string, Layer 3 Layer Diel. string, Layer 3 Depth(in) string, Layer 4 2-Way Time string, Layer 4 Layer Diel. string, Layer 4 Depth(in) string
    -> AttributeManager
AttributeManager
    ATTR_TABLE:
      RENAME_SET_VALUE Lat(°) > Lat
      RENAME_SET_VALUE Long(°) > Long
      RENAME_SET_VALUE Layer 1 2-Way Time > Layer1-2WayTime
      RENAME_SET_VALUE Layer 1 Layer Diel. > Layer1-DielectricConstant
      RENAME_SET_VALUE Layer 2 2-Way Time > Layer2-2WayTime
      RENAME_SET_VALUE Layer 2 Layer Diel. > Layer2-DielectricConstant
      RENAME_SET_VALUE Layer 3 2-Way Time > Layer3-2WayTime
      RENAME_SET_VALUE Layer 3 Layer Diel. > Layer3-DielectricConstant
      RENAME_SET_VALUE Layer 4 2-Way Time > Layer4-2WayTime
      RENAME_SET_VALUE Layer 4 Layer Diel. > Layer4-DielectricConstant
      RENAME_SET_VALUE fme_basename > SourceFilename
      RENAME_SET_VALUE Layer 1 Depth(in) > Layer1-Depth
      RENAME_SET_VALUE Layer 2 Depth(in) > Layer2-Depth
      RENAME_SET_VALUE Layer 3 Depth(in) > Layer3-Depth
      RENAME_SET_VALUE Layer 4 Depth(in) > Layer4-Depth
    -> VertexCreator
VertexCreator
    MODE_NAME = Replace with Point
    XVAL = @Value(IDSession)
    YVAL = @Value(DistanceStamp)
    -> Tester_4
Tester_4
    BOOL_OP = OR
    TEST_CLAUSE = TEST @Value(Layer1-Depth) > 0
    PASSED -> AttributeCreator_4
    FAILED -> Tester_8
Tester_8
    BOOL_OP = AND
    TEST_CLAUSE:
      TEST @Value(Layer1-2WayTime) > 0
      TEST @Value(Layer1-DielectricConstant) > 0
    PASSED -> AttributeCreator_6
    FAILED -> Tester_9
AttributeCreator_6
    ATTR_TABLE = SET_TO Layer1-Depth = @Evaluate(6.55*@Value(Layer1-2WayTime))
    -> AttributeRounder
AttributeRounder
    PLACES = 2
    ROUND_TYPE = Nearest
    SRC_ATTRS = Layer1-Depth
    -> AttributeCreator_4
Tester_9
    BOOL_OP = AND
    TEST_CLAUSE:
      TEST @Value(Layer2-2WayTime) > 0
      TEST @Value(Layer2-DielectricConstant) > 0
    PASSED -> AttributeCreator_5
    FAILED -> DuplicateFilter
AttributeCreator_5
    ATTR_TABLE:
      SET_TO Layer1-2WayTime = @Value(Layer2-2WayTime)
      SET_TO Layer1-Depth = @Value(Layer2-Depth)
      SET_TO Layer1-DielectricConstant = @Value(Layer2-DielectricConstant)
    -> AttributeCreator_8
AttributeCreator_8
    ATTR_TABLE:
      SET_TO Layer2-2WayTime = @Value(Layer3-2WayTime)
      SET_TO Layer2-Depth = @Value(Layer3-Depth)
      SET_TO Layer2-DielectricConstant = @Value(Layer3-DielectricConstant)
    -> AttributeCreator_4
AttributeCreator_4
    ATTR_TABLE:
      SET_TO Layer1-Thickness = @Value(Layer1-Depth)
      SET_TO Layer2-Thickness = @Evaluate(@Value(Layer2-Depth)-@Value(Layer1-Depth))
      SET_TO Layer3-Thickness = FME_CONDITIONAL:DEFAULT_VALUE'_FME_NO_OP_'BOOL_OP;OR;COMPOSITE_TEST;<Unused>;TEST @Value(Layer3-DielectricConstant) > 0'@Evaluate(@Value(Layer3-Depth)-@Value(Layer2-Depth))'FME_NUM_CONDITIONS2___
      SET_TO Layer4-Thickness = FME_CONDITIONAL:DEFAULT_VALUE'_FME_NO_OP_'BOOL_OP;OR;COMPOSITE_TEST;<Unused>;TEST @Value(Layer4-DielectricConstant) > 0'@Evaluate(@Value(Layer4-Depth)-@Value(Layer3-Depth))'FME_NUM_CONDITIONS2___
    -> AttributeCreator
AttributeCreator
    ATTR_TABLE:
      SET_TO Layer1-Material = FME_CONDITIONAL:DEFAULT_VALUE'_FME_NO_OP_'BOOL_OP;OR;COMPOSITE_TEST;<Unused>;TEST @Value(Layer1-DielectricConstant) < 5'AC-Surface'BOOL_OP;OR;COMPOSITE_TEST;<Unused>;TEST @Value(Layer1-DielectricConstant) < 7.5'AC-Dense Graded'BOOL_OP;OR;COMPOSITE_TEST;<Unused>;TEST @Value(Layer1-DielectricConstant) < 8.5'PCC'FME_NUM_CONDITIONS4___
      SET_TO Layer2-Material = FME_CONDITIONAL:DEFAULT_VALUE'_FME_NO_OP_'BOOL_OP;OR;COMPOSITE_TEST;<Unused>;TEST @Value(Layer2-DielectricConstant) < 7.5'AC-Dense Graded'BOOL_OP;OR;COMPOSITE_TEST;<Unused>;TEST @Value(Layer2-DielectricConstant) < 8.5'PCC/AC'BOOL_OP;OR;COMPOSITE_TEST;<Unused>;TEST @Value(Layer2-DielectricConstant) < 10.5'Base'FME_NUM_CONDITIONS4___
      SET_TO Layer3-Material = FME_CONDITIONAL:DEFAULT_VALUE'_FME_NO_OP_'BOOL_OP;OR;COMPOSITE_TEST;<Unused>;TEST @Value(Layer3-DielectricConstant) > 8'Base'FME_NUM_CONDITIONS2___
      SET_TO Layer4-Material
      SET_TO Filename = Hempstead_GPR_remainingMissed0502
    -> All2 (writer CSV2_2)
All2 (writer CSV2_2)
    attributes: IDSession string, DistanceStamp string, Scan string, Lat string, Long string, Layer1-Depth string, Layer1-Material string, Layer1-Thickness string, Layer1-2WayTime string, Layer1-DielectricConstant string, Layer2-Depth string, Layer2-Material string, Layer2-Thickness string, Layer2-2WayTime string, Layer2-DielectricConstant string, Layer3-Depth string, Layer3-Material string, Layer3-Thickness string, Layer3-2WayTime string, Layer3-DielectricConstant string, Layer4-Depth string, Layer4-Material string, Layer4-Thickness string, Layer4-2WayTime string, Layer4-DielectricConstant string, SourceFilename string
DuplicateFilter
    INPUT_ORDERED_CHOICE = No
    KEYATTR = SourceFilename
    UNIQUE -> Tester_9_Failed
Tester_9_Failed: Inspector [off]
