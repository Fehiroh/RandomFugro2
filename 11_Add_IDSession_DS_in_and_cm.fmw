FME workspace 11_Add_IDSession_DS_in_and_cm.fmw

Parameters:
- DestDataset_CSV2 = $(FME_MF_DIR)csv_afterGPR   # Destination CSV (Comma Separated Value) Folder
- SourceDataset_CSV2 = $(FME_MF_DIR)Weekly_deliveries\Round 1\**\*.csv   # Source CSV (Comma Separated Value) File(s)
- SourceDataset_GEODATABASE_FILE = $(FME_MF_DIR)Matches_and_RawGPR.gdb   # File Geodatabase

Readers:
- CSV2_1: CSV2 from $(SourceDataset_CSV2)
- GEODATABASE_FILE_1: GEODATABASE_FILE from $(SourceDataset_GEODATABASE_FILE)

Writers:
- CSV2_2: CSV2 to $(DestDataset_CSV2)

Matches (reader GEODATABASE_FILE_1)
    attributes: OBJECTID integer, idmatch char(200), IDSession char(200), UniqueRun char(200), date char(200), BeginDistanceStamp char(200), EndDistanceStamp char(200), Status char(200), SHAPE_Length double
    -> Tester
Tester
    BOOL_OP = OR
    TEST_CLAUSE = TEST @Value(Status) = Matched
    PASSED -> PointOnLineOverlayer_2 [LINE]
    PASSED -> AnchoredSnapper [ANCHOR]
    PASSED -> PointOnLineOverlayer [LINE]
CSV (reader CSV2_1)
    attributes: Dist.(m) string, Scan string, Lat(°) string, Long(°) string, Layer 1 Vel. Method string, Layer 1 2-Way Time string, Layer 1 Depth(cm) string, Layer 1 Layer Diel. string, Layer 2 Vel. Method string, Layer 2 2-Way Time string, Layer 2 Depth(cm) string, Layer 2 Layer Diel. string, Layer 3 Vel. Method string, Layer 3 2-Way Time string, Layer 3 Depth(cm) string, Layer 3 Layer Diel. string, Layer 4 Vel. Method string, Layer 4 2-Way Time string, Layer 4 Depth(cm) string, Layer 4 Layer Diel. string, col20 string
    -> AttributeCreator
AttributeCreator
    ATTR_TABLE:
      SET_TO Layer 1 Depth(in) = @Evaluate(@Value(Layer 1 Depth(cm))/2.54)
      SET_TO Layer 2 Depth(in) = @Evaluate(@Value(Layer 2 Depth(cm))/2.54)
      SET_TO Layer 3 Depth(in) = FME_CONDITIONAL:DEFAULT_VALUE'_FME_NO_OP_'BOOL_OP;OR;COMPOSITE_TEST;<Unused>;TEST @Value(Layer 3 Depth(cm)) > 0'@Evaluate(@Value(Layer 3 Depth(cm))/2.54)'FME_NUM_CONDITIONS2___
      SET_TO Layer 4 Depth(in) = FME_CONDITIONAL:DEFAULT_VALUE'_FME_NO_OP_'BOOL_OP;OR;COMPOSITE_TEST;<Unused>;TEST @Value(Layer 4 Depth(cm)) > 0'@Evaluate(@Value(Layer 4 Depth(cm))/2.54)'FME_NUM_CONDITIONS2___
    -> StatisticsCalculator_2
StatisticsCalculator_2
    COMPUTE_HISTOGRAM = NO
    COUNT_ATTR = _csv_Count
    PREPEND_ATTR_NAME_CHOICE = For multiple results only
    STATS_ATTRS = fme_basename
    COMPLETE -> VertexCreator
VertexCreator
    MODE_NAME = Add Point
    XVAL = @Value(Long(°))
    YVAL = @Value(Lat(°))
    -> AnchoredSnapper [CANDIDATE]
AnchoredSnapper
    CLEANING_TOLERANCE = Automatic
    SNAPTYPE_PARAM = Segment Snapping
    TOLERANCE = 0.00005
    SNAPPED -> Junction
    UNTOUCHED -> Junction
Junction
    -> FeatureMerger [REQUESTOR]
    -> PointOnLineOverlayer [POINT]
PointOnLineOverlayer
    DEAGGREGATE_INPUT = Yes
    LIST_ATTRS_TO_INCLUDE = BeginDistanceStamp date EndDistanceStamp idmatch IDSession OBJECTID SHAPE_Length Status UniqueRun
    LIST_NAME = Line
    OV_ATTR = _overlaps
    TOLERANCE = 0.000001
    POINT -> ListExploder
ListExploder
    ATTR_ACCUM_MODE = Prefix List Attributes
    INCOMING_PREFIX = Line_
    INDEX_ATTR = _element_index
    LIST_ATTR = Line{}
    ELEMENTS -> StatisticsCalculator
StatisticsCalculator
    COMPUTE_HISTOGRAM = NO
    COUNT_ATTR = _count
    GROUP_BY = Line_IDSession _csv_Count Line_idmatch fme_basename
    PREPEND_ATTR_NAME_CHOICE = For multiple results only
    STATS_ATTRS = Line_idmatch
    SUMMARY -> Sorter
Sorter
    SORT_PARM = fme_basename ALPHA ASCENDING _count NUMERIC DESCENDING
    SORTED -> DuplicateFilter
DuplicateFilter
    INPUT_ORDERED_CHOICE = No
    KEYATTR = fme_basename
    UNIQUE -> AttributeKeeper
    DUPLICATE -> Tester_3
Tester_3
    BOOL_OP = OR
    TEST_CLAUSE = TEST @Value(_count) > 5
    PASSED -> AttributeKeeper
    FAILED -> Less_than_5_points_in_overlap
AttributeKeeper
    KEEP_ATTRS = Line_IDSession,Line_idmatch,fme_basename
    -> AttributeRenamer
AttributeRenamer
    ATTR_TABLE = RENAME_SET_DEFAULT Line_idmatch > idmatch
    -> FeatureMerger [SUPPLIER]
FeatureMerger
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(fme_basename) @Value(fme_basename) AUTO
    LIST_ATTRS_TO_INCLUDE = idmatch
    LIST_NAME = sup_
    MERGE_TYPE = Attributes Only
    PROCESS_DUPS = YES
    REJECT_NULL_MISSING_KEYS = No
    SUPPLIERS_FIRST = No
    MERGED -> ListExploder_3
ListExploder_3
    ATTR_ACCUM_MODE = Merge List Attributes
    ATTR_CONFLICT_RES = Use List Attribute Values
    INDEX_ATTR = _element_index
    LIST_ATTR = sup_{}
    ELEMENTS -> PointOnLineOverlayer_2 [POINT]
PointOnLineOverlayer_2
    DEAGGREGATE_INPUT = Yes
    GROUP_BY = idmatch
    LIST_ATTRS_TO_INCLUDE = BeginDistanceStamp date EndDistanceStamp idmatch IDSession OBJECTID SHAPE_Length Status UniqueRun
    LIST_NAME = Line
    OV_ATTR = _overlaps
    TOLERANCE = 0.000001
    POINT -> Tester_2
Tester_2
    BOOL_OP = OR
    TEST_CLAUSE = TEST @Value(_overlaps) > 0
    PASSED -> ListExploder_2
ListExploder_2
    ATTR_ACCUM_MODE = Prefix List Attributes
    INCOMING_PREFIX = Line_
    INDEX_ATTR = _element_index
    LIST_ATTR = Line{}
    ELEMENTS -> AttributeRenamer_2
AttributeRenamer_2
    ATTR_TABLE = RENAME_SET_DEFAULT Line_IDSession > IDSession
    -> CoordinateExtractor
CoordinateExtractor
    IND = 0
    MODE = Specify Coordinate
    Z_ATTR = DistanceStamp
    -> AttributeRounder
AttributeRounder
    PLACES = 3
    ROUND_TYPE = Nearest
    SRC_ATTRS = DistanceStamp
    -> AttributeRemover
AttributeRemover
    REMOVE_ATTRS = Dist.(m),_overlaps,Line_OBJECTID,Line_UniqueRun,_element_index,Line_EndDistanceStamp,Line_IDSession,Line_idmatch,Line_SHAPE_Length,Line_Status,Line_BeginDistanceStamp,Line_date,_csv_Count
    -> DuplicateFilter_2
DuplicateFilter_2
    INPUT_ORDERED_CHOICE = No
    KEYATTR = fme_basename Scan
    UNIQUE -> CSV (writer CSV2_2)
CSV (writer CSV2_2)
    attributes: IDSession string, DistanceStamp string, Scan string, Lat(°) string, Long(°) string, Layer 1 2-Way Time string, Layer 1 Layer Diel. string, Layer 1 Depth(in) string, Layer 2 2-Way Time string, Layer 2 Layer Diel. string, Layer 2 Depth(in) string, Layer 3 2-Way Time string, Layer 3 Layer Diel. string, Layer 3 Depth(in) string, Layer 4 2-Way Time string, Layer 4 Layer Diel. string, Layer 4 Depth(in) string
Less_than_5_points_in_overlap: Inspector
